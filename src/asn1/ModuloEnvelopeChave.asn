-- ModuloEnvelopeChave.asn
-- Reconstructed from vota_web_wasm.wasm (TSE voting-simulator build of VOTA, "10.23.0.1 - DESENVOLVIMENTO")
-- by reading the III ASN.1 runtime tables (SEQUENCE/CHOICE/ENUMERATED InfoType structs) in linear memory.
-- See docs/data-model/asn1-schemas.md for the method and for what each module means.
--
-- Confidence:
--  * member names, order, OPTIONAL, tags, INTEGER ranges, SIZE constraints, ENUMERATED names and
--    numbers: HIGH (read directly from the tables the encoder/decoder uses);
--  * type names: see the 'info @addr; name: <source>' comment above each definition:
--      infoname = the name string TSE added to every SEQUENCE InfoType (+48), rtti = C++ class
--      name (typeinfo) bound to the table, srcloc = name found in a source_location signature,
--      spec = name used by the TSE published spec for an identical type, inferred = placeholder;
--  * the module header (IMPLICIT TAGS) and the IMPORTS lists are reconstructed, not read;
--  * constrained INTEGER typedef names (QtdEleitores, NumeroZona...) do not exist in the binary
--    (III ASN.1 turns them into shared C++ template instances), so ranges are written inline;
--    when the TSE published spec (v2, 2024) names the type of a field we add a 'spec: Name' comment.

-- Key envelope (EntidadeChave): a secret or public key with its owner descriptor.

ModuloEnvelopeChave DEFINITIONS IMPLICIT TAGS ::= BEGIN

-- info @1146940; name: rtti+infoname (high)
EntidadeChave ::= SEQUENCE {
    tagChaves                              NumericString (SIZE(12)),                             -- shared string typedef @1913028, name unknown
    descritor                              DescritorChave,
    cifrado                                BOOLEAN,
    tipo                                   TipoChave,
    chave                                  OCTET STRING
}

-- info @1146864; name: infoname (high); module: inferred from the types that use it
DescritorChave ::= SEQUENCE {
    nomeUsuario                            GeneralString,
    serial                                 INTEGER
}

-- info @1146916; name: inferred (low) <<< placeholder name, not in the binary; module: inferred from the types that use it
TipoChave ::= ENUMERATED {
    chaveSecreta (0),
    chavePublica (1)
}

END
