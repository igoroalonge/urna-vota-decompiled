-- ModuloTiposResultadosEcoUrna.asn
-- Reconstructed from vota_web_wasm.wasm (TSE voting-simulator build of VOTA, "10.23.0.1 - DESENVOLVIMENTO")
-- by reading the III ASN.1 runtime tables (SEQUENCE/CHOICE/ENUMERATED InfoType structs) in linear memory.
-- See docs/data-model/asn1-schemas.md for the method and for what each module means.
--
-- Confidence:
--  * member names, order, OPTIONAL, tags, INTEGER ranges, SIZE constraints, ENUMERATED names and
--    numbers: HIGH (read directly from the tables the encoder/decoder uses);
--  * type names: see the 'info @addr; name: <source>' comment above each definition:
--      infoname = the name string TSE added to every SEQUENCE InfoType (+48), rtti = C++ class
--      name (typeinfo) bound to the table, srcloc = name found in a source_location signature,
--      spec = name used by the TSE published spec for an identical type, inferred = placeholder;
--  * the module header (IMPLICIT TAGS) and the IMPORTS lists are reconstructed, not read;
--  * constrained INTEGER typedef names (QtdEleitores, NumeroZona...) do not exist in the binary
--    (III ASN.1 turns them into shared C++ template instances), so ranges are written inline;
--    when the TSE published spec (v2, 2024) names the type of a field we add a 'spec: Name' comment.

-- Types shared by result files: Urna (type, software version, correspondence, file type), Sistema de Apuracao reasons.

ModuloTiposResultadosEcoUrna DEFINITIONS IMPLICIT TAGS ::= BEGIN

IMPORTS
    Carga
        FROM ModuloTiposEcoUrna
    IdentificacaoUrna
        FROM ModuloTiposEleitorais;

-- info @1144572; name: rtti+infoname (high)
ApuracaoEletronica ::= SEQUENCE {
    tipoapuracao                           TipoApuracao,
    motivoApuracao                         MotivoApuracaoEletronica
}

-- info @1144468; name: rtti+infoname (high)
ApuracaoMistaBUAE ::= SEQUENCE {
    tipoapuracao                           TipoApuracao,
    motivoApuracao                         MotivoApuracaoMistaComBU
}

-- info @1144416; name: rtti+infoname (high)
ApuracaoMistaMR ::= SEQUENCE {
    tipoApuracao                           TipoApuracao,
    motivoApuracao                         MotivoApuracaoMistaComMR
}

-- info @1144520; name: rtti+infoname (high)
ApuracaoTotalmenteManualDigitacaoAE ::= SEQUENCE {
    tipoapuracao                           TipoApuracao,
    motivoApuracao                         MotivoApuracaoManual
}

-- info @1144196; name: rtti+infoname (high)
CorrespondenciaResultado ::= SEQUENCE {
    identificacao                          IdentificacaoUrna,
    carga                                  Carga
}

-- info @1144660; name: rtti+infoname (high)
Urna ::= SEQUENCE {
    tipoUrna                               TipoUrna,
    versaoVotacao                          GeneralString,
    correspondenciaResultado               CorrespondenciaResultado,
    tipoArquivo                            TipoArquivo,
    numeroSerieFV                          OCTET STRING (SIZE(4)),                               -- spec: NumeroSerieFlash
    motivoUtilizacaoSA                     TipoApuracaoSA OPTIONAL
}

-- info @1144624; name: rtti (high)
TipoApuracaoSA ::= CHOICE {
    apuracaoMistaMR                        [0] ApuracaoMistaMR,
    apuracaoMistaBUAE                      [1] ApuracaoMistaBUAE,
    apuracaoTotalmenteManual               [2] ApuracaoTotalmenteManualDigitacaoAE,
    apuracaoEletronica                     [3] ApuracaoEletronica
}

-- info @1144392; name: rtti (high)
MotivoApuracaoEletronica ::= ENUMERATED {
    naoFoiPossivelReuperarResultado (1),
    urnaNaoChegouMidiaDefeituosa (2),
    urnaNaoChegouMidiaExtraviada (3),
    outros (99)
}

-- info @1144320; name: rtti (high)
MotivoApuracaoManual ::= ENUMERATED {
    urnaComDefeito (1),
    urnaIndisponivelInicio (2),
    urnaOutraSecao (3),
    outros (99)
}

-- info @1144368; name: rtti (high)
MotivoApuracaoMistaComBU ::= ENUMERATED {
    urnaDataHoraIncorreta (1),
    urnaComDefeito (2),
    urnaOutrasecao (3),
    urnaPreparadaIncorretamente (4),
    urnaEncerradaComEleitoresNaFila (5),
    outros (99)
}

-- info @1144344; name: rtti (high)
MotivoApuracaoMistaComMR ::= ENUMERATED {
    naoObteveExitoContingencia (1),
    indisponibilidadeUrnaContingencia (2),
    indisponibilidadeFlashContingencia (3),
    problemaEnergiaEletrica (4),
    naoFoiPossivelTrocarUrna (5),
    naoFoiSolicitadaTrocaUrna (6),
    outros (99)
}

-- info @1144296; name: spec (high); module: inferred from the types that use it
TipoApuracao ::= ENUMERATED {
    totalmenteManual (1),
    totalmenteEletronica (2),
    mistaBU (3),
    mistaMR (4)
}

-- info @1144248; name: srcloc (high)
TipoArquivo ::= ENUMERATED {
    votacaoUE (1),
    votacaoRED (2),
    saMistaMRParcialCedula (3),
    saMistaBUImpressoCedula (4),
    saManual (5),
    saEletronica (6)
}

-- info @1144272; name: srcloc (high)
TipoUrna ::= ENUMERATED {
    secao (1),
    contingencia (3),
    contingenciaSecao (4),
    contingenciaEncerrandoSecao (6)
}

END
