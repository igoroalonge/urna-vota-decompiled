-- ModuloImpedidos.asn
-- Reconstructed from vota_web_wasm.wasm (TSE voting-simulator build of VOTA, "10.23.0.1 - DESENVOLVIMENTO")
-- by reading the III ASN.1 runtime tables (SEQUENCE/CHOICE/ENUMERATED InfoType structs) in linear memory.
-- See docs/data-model/asn1-schemas.md for the method and for what each module means.
--
-- Confidence:
--  * member names, order, OPTIONAL, tags, INTEGER ranges, SIZE constraints, ENUMERATED names and
--    numbers: HIGH (read directly from the tables the encoder/decoder uses);
--  * type names: see the 'info @addr; name: <source>' comment above each definition:
--      infoname = the name string TSE added to every SEQUENCE InfoType (+48), rtti = C++ class
--      name (typeinfo) bound to the table, srcloc = name found in a source_location signature,
--      spec = name used by the TSE published spec for an identical type, inferred = placeholder;
--  * the module header (IMPLICIT TAGS) and the IMPORTS lists are reconstructed, not read;
--  * constrained INTEGER typedef names (QtdEleitores, NumeroZona...) do not exist in the binary
--    (III ASN.1 turns them into shared C++ template instances), so ranges are written inline;
--    when the TSE published spec (v2, 2024) names the type of a field we add a 'spec: Name' comment.

-- Voters impeded from voting in this section (impedidos), file *-imp.dat.

ModuloImpedidos DEFINITIONS IMPLICIT TAGS ::= BEGIN

IMPORTS
    CabecalhoEntidade, IdentificacaoSecaoEleitoral, IdentificadorEleitor
        FROM ModuloTiposEleitorais;

-- info @1142468; name: rtti+infoname (high)
EntidadeImpedidos ::= SEQUENCE {
    cabecalho                              CabecalhoEntidade,
    identificacao                          IdentificacaoSecaoEleitoral,
    eleitores                              SEQUENCE OF EleitorImpedido OPTIONAL
}

-- info @1142384; name: infoname (high); module: inferred from the types that use it
EleitorImpedido ::= SEQUENCE {
    identificadorEleitor                   IdentificadorEleitor,
    impedimentoP1                          TipoImpedimento,
    impedimentoP2                          TipoImpedimento OPTIONAL
}

-- info @1142360; name: rtti-struct (high)
TipoImpedimento ::= ENUMERATED {
    semImpedimento (1),
    votaNaSecaoOriginal (2),
    solicitouVotoEmTransito (3),
    presoProvisorio (4),
    suspenso (5),
    cancelado (6),
    naoLiberado (7),
    semIdadeMinima (8),
    militarEmServico (9),
    tteAcessibilidade (10),
    tteEleitorConvocado (11),
    tteJusticaEleitoral (12),
    tteOficio (13),
    tteIndigenasQuilombolas (14),
    tteSituacaoRua (15)
}

END
