-- ModuloTiposCadastro.asn
-- Reconstructed from vota_web_wasm.wasm (TSE voting-simulator build of VOTA, "10.23.0.1 - DESENVOLVIMENTO")
-- by reading the III ASN.1 runtime tables (SEQUENCE/CHOICE/ENUMERATED InfoType structs) in linear memory.
-- See docs/data-model/asn1-schemas.md for the method and for what each module means.
--
-- Confidence:
--  * member names, order, OPTIONAL, tags, INTEGER ranges, SIZE constraints, ENUMERATED names and
--    numbers: HIGH (read directly from the tables the encoder/decoder uses);
--  * type names: see the 'info @addr; name: <source>' comment above each definition:
--      infoname = the name string TSE added to every SEQUENCE InfoType (+48), rtti = C++ class
--      name (typeinfo) bound to the table, srcloc = name found in a source_location signature,
--      spec = name used by the TSE published spec for an identical type, inferred = placeholder;
--  * the module header (IMPLICIT TAGS) and the IMPORTS lists are reconstructed, not read;
--  * constrained INTEGER typedef names (QtdEleitores, NumeroZona...) do not exist in the binary
--    (III ASN.1 turns them into shared C++ template instances), so ranges are written inline;
--    when the TSE published spec (v2, 2024) names the type of a field we add a 'spec: Name' comment.

-- Registry types: Municipio, TipoLocalVotacao.

ModuloTiposCadastro DEFINITIONS IMPLICIT TAGS ::= BEGIN

-- info @1143564; name: rtti+infoname (high)
Municipio ::= SEQUENCE {
    codigo                                 INTEGER (1..99999),
    nome                                   GeneralString (SIZE(1..35)),
    capital                                BOOLEAN,
    codigoIBGE                             [1] INTEGER (1100000..9999999) OPTIONAL,
    comBiometria                           [2] BOOLEAN OPTIONAL
}

-- info @1143440; name: rtti (high)
TipoLocalVotacao ::= ENUMERATED {
    normal (1),
    emTransito (2),
    presoProvisorio (3),
    temporario (4)
}

END
