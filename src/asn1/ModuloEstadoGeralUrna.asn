-- ModuloEstadoGeralUrna.asn
-- Reconstructed from vota_web_wasm.wasm (TSE voting-simulator build of VOTA, "10.23.0.1 - DESENVOLVIMENTO")
-- by reading the III ASN.1 runtime tables (SEQUENCE/CHOICE/ENUMERATED InfoType structs) in linear memory.
-- See docs/data-model/asn1-schemas.md for the method and for what each module means.
--
-- Confidence:
--  * member names, order, OPTIONAL, tags, INTEGER ranges, SIZE constraints, ENUMERATED names and
--    numbers: HIGH (read directly from the tables the encoder/decoder uses);
--  * type names: see the 'info @addr; name: <source>' comment above each definition:
--      infoname = the name string TSE added to every SEQUENCE InfoType (+48), rtti = C++ class
--      name (typeinfo) bound to the table, srcloc = name found in a source_location signature,
--      spec = name used by the TSE published spec for an identical type, inferred = placeholder;
--  * the module header (IMPLICIT TAGS) and the IMPORTS lists are reconstructed, not read;
--  * constrained INTEGER typedef names (QtdEleitores, NumeroZona...) do not exist in the binary
--    (III ASN.1 turns them into shared C++ template instances), so ranges are written inline;
--    when the TSE published spec (v2, 2024) names the type of a field we add a 'spec: Name' comment.

-- Persistent state of the urna (eg.bin).

ModuloEstadoGeralUrna DEFINITIONS IMPLICIT TAGS ::= BEGIN

IMPORTS
    TipoLocalVotacao
        FROM ModuloTiposCadastro
    Carga, ModeloEquipamento
        FROM ModuloTiposEcoUrna
    Fase, SiglaUF, Turno
        FROM ModuloTiposEleitorais;

-- info @1146012; name: rtti+infoname (high)
EstadoGeralUrna ::= SEQUENCE {
    idPE                                   INTEGER (0..99999),
    estadoUrna                             EstadoUrna,
    dadoCarga                              DadoCarga,
    dadoLocal                              DadoLocal,
    ajusteDataHora                         AjusteDataHora,
    correspondencia                        DadoCorrespondencia,
    versao                                 GeneralString,
    hashVersoesPacotes                     OCTET STRING
}

-- info @1145960; name: rtti+infoname (high)
AjusteDataHora ::= SEQUENCE {
    tipoAjusteDataHora                     TipoAjusteDataHora,
    valorAjusteDataHora                    INTEGER
}

-- info @1145908; name: rtti+infoname (high)
DadoCarga ::= SEQUENCE {
    turno                                  Turno,
    tipoUrnaT1                             TipoUrnaOperacao,
    tipoUrnaT2                             TipoUrnaOperacao,
    modelo                                 ModeloEquipamento,
    fase                                   Fase
}

-- info @1145784; name: rtti+infoname (high)
DadoCorrespondencia ::= SEQUENCE {
    carga                                  Carga,
    secaoCarga                             DadoSecao,
    assinatura                             OCTET STRING
}

-- info @1145732; name: rtti+infoname (high)
DadoLocal ::= SEQUENCE {
    uf                                     SiglaUF,
    secaoCarga                             DadoSecao,
    tipoLocalVotacao                       TipoLocalVotacao
}

-- info @1145680; name: rtti+infoname (high)
DadoSecao ::= SEQUENCE {
    municipio                              INTEGER (1..99999),
    zona                                   INTEGER (1..9999),
    secao                                  INTEGER (0..9999)
}

-- info @1145836; name: rtti (high)
EstadoUrna ::= ENUMERATED {
    carregando (1),
    carregada (2),
    testada (3)
}

-- info @1145884; name: rtti (high)
TipoAjusteDataHora ::= ENUMERATED {
    semAjusteDataHora (1),
    alterarDataEleicao (2),
    alterarDataSistema (3)
}

-- info @1145860; name: rtti (high)
TipoUrnaOperacao ::= ENUMERATED {
    semtipo (0),
    vota (1),
    contingencia (2),
    contingenciavota (3),
    contingenciavotarecupera (4)
}

END
