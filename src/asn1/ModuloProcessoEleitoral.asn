-- ModuloProcessoEleitoral.asn
-- Reconstructed from vota_web_wasm.wasm (TSE voting-simulator build of VOTA, "10.23.0.1 - DESENVOLVIMENTO")
-- by reading the III ASN.1 runtime tables (SEQUENCE/CHOICE/ENUMERATED InfoType structs) in linear memory.
-- See docs/data-model/asn1-schemas.md for the method and for what each module means.
--
-- Confidence:
--  * member names, order, OPTIONAL, tags, INTEGER ranges, SIZE constraints, ENUMERATED names and
--    numbers: HIGH (read directly from the tables the encoder/decoder uses);
--  * type names: see the 'info @addr; name: <source>' comment above each definition:
--      infoname = the name string TSE added to every SEQUENCE InfoType (+48), rtti = C++ class
--      name (typeinfo) bound to the table, srcloc = name found in a source_location signature,
--      spec = name used by the TSE published spec for an identical type, inferred = placeholder;
--  * the module header (IMPLICIT TAGS) and the IMPORTS lists are reconstructed, not read;
--  * constrained INTEGER typedef names (QtdEleitores, NumeroZona...) do not exist in the binary
--    (III ASN.1 turns them into shared C++ template instances), so ranges are written inline;
--    when the TSE published spec (v2, 2024) names the type of a field we add a 'spec: Name' comment.

-- The processo eleitoral (1st/2nd pleito, main election type, allowed TTE types...). *-cp.dat.

ModuloProcessoEleitoral DEFINITIONS IMPLICIT TAGS ::= BEGIN

IMPORTS
    CabecalhoEntidade, DataJE, SiglaUF, TipoAbrangencia, TipoEleicao, TipoIdentificadorEleitor, TipoTransferenciaTemporaria
        FROM ModuloTiposEleitorais;

-- info @1145528; name: rtti+infoname (high)
EntidadeProcessoEleitoral ::= SEQUENCE {
    cabecalho                              CabecalhoEntidade,
    nome                                   GeneralString (SIZE(1..38)),
    dataEleitorado                         DataJE OPTIONAL,
    pleito1                                Pleito,
    pleito2                                Pleito OPTIONAL,
    tipoEleicaoPrincipal                   TipoEleicao,
    abrangenciaEleicaoPrincipal            TipoAbrangencia,
    permiteMRJ                             BOOLEAN,
    utilizaBiometria                       BOOLEAN,
    tiposTTEPermitidos                     SEQUENCE OF TipoTransferenciaTemporaria,
    tipoIdentificadorPrincipalEleitor      TipoIdentificadorEleitor,
    tiposIdentificadoresPermitidos         SEQUENCE OF TipoIdentificadorEleitor,
    origemConfiguracao                     OrigemConfiguracao,
    ufs                                    SEQUENCE OF SiglaUF
}

-- info @1145356; name: infoname (high)
Pleito ::= SEQUENCE {
    id                                     INTEGER (0..99999),
    nome                                   GeneralString (SIZE(1..38)),
    data                                   DataJE
}

-- info @1145408; name: rtti (high)
OrigemConfiguracao ::= ENUMERATED {
    oficial (1),
    comunitaria (2)
}

END
